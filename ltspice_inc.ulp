#usage "The goal of this include file is to seperate the os-specific parts from the main Ltspice.ulp"
       "In this way I can focus any portability efforts on just this one file."
       "10/31/2016"
       "<author>Author:Alfred Zaffran, alf@cadsoft.de</author>"
       "<author>Author:Jorge Garcia, jorge.garcia@autodesk.com</author>"

/**********************************************************************************************************************
*                                               FILE FUNCTIONS                                                        *
**********************************************************************************************************************/

string OS="";   //This variable will define what OS the ULP is being run under WINDOWS, LINUX, MAC JG 11/10/2016

// This function checks what operating system this ULP is running on. Verified 11/10/2016
void operatingsystem(void) {
  int discover;

  discover = strstr(OS_SIGNATURE, "Windows");
  if (discover < 0) {
    discover = strstr(OS_SIGNATURE, "Linux");
    if (discover < 0) {
      OS = "MAC";
    }
    else {
      OS = "LINUX";
    }
  }
  else {
    OS = "WINDOWS";
  }
}

int check_files(string path, string file_ext) {
  return fileglob(SearchFiles, path + file_ext);
}

string is_WINE_in_use(void) {
  if (OS == "WINDOWS") {  //Windows doesn't need WINE so always return 0
    return "0";
  }
  if (OS == "LINUX") {  //LTSpice in Linux always requires WINE so return 1
    return "1";
  }
  if (OS == "MAC") { //Newer versions of LTSpice can run natively on Mac, older versions require WINE.
    if (dlgMessageBox("Are you running LTSpice under WINE?", "&Yes", "&No") == 0) {
      return "1";
    }
    else {
      return "0";
    }
  }
}

// ein Windows-Laufwerk beginnt mit "Buchstabe:\"
// suche nach ":/" hinter dem Laufwerksbuchstaben
void check_windows_root(void) {
  string drv;
  for(int d = SearchStartDrive; d <= SearchLastDrive; d++) {
    sprintf(drv, "%c:/", d);
    if (check_files(drv, "/")) {
      SearchRoot[SearchnRoot] = drv;
      SearchnRoot++;
    }
  }
  return;
}

/************************ die Suchschleife *******************************************************/
// searchfile   = die zu suchende Datei
// root         = der Start-Pfad ab dem gesucht werden soll, inkl. Laufwerkbuchstabe unter Windows
// maxiteration = die Tiefe, Anzahl der Verzweigung (Unterordner) ab dem root Pfad.

// As it turns out there is really nothing OS-specific about this function, by having the user
// specify a few locations, I've avoided having to modify this file at all. JG 11/18/2016
/*************************************************************************************************/
string file_search(string searchfile, string root, int maxiteration, string debugnum) {
  if (!root) {
    if (debugnum == "init") {
      dlgMessageBox("RUN ltspice.ulp with option Setup: "+searchfile, "CANCEL");
    }
    else {
      if (dlgMessageBox(debugnum + "\nUnknown path of file : "+searchfile, "OK", "CANCEL") == 0) return "";
    }
    exit(-752);
  }
  int len = strlen(root);
  if (root[len-1] != '/') root += "/"; // root muß mit Slash enden! Eng: Root path must end in slash
  if (!check_files(root, "")) {  // den Pfad prüfen Eng: Make sure it's not empty
    return "";
  }
  // *** Betriebsystem feststellen ***
  // ******* Windows Laufwerke *******
  if (root) { //Root Directory has been found
    SearchRoot[0] = root;
    SearchnRoot = 1;
  }
  else { //Empty root directory
    check_windows_root();   // unter Windows die Laufwerke ermitteln
    //if (SearchnRoot) {
    //  sprintf(SearchRootfound, "Betriebssystem WINDOWS");
    //  for (int d = 0; d < SearchnRoot; d++) {
    //   SearchRootfound += SearchRoot[d] + "\n";
    //  }
    //}
    //int pos;
    // ************* Windows UNC-Pfad *****************
    //pos = strstr(root, "//", 0);  // windows hat bei UNC Namen zweimal Slash // am Anfang
    //check_UNC(root);
    //if (!SearchIs_UNC) if (project.board) project.board(B) check_UNC(B.name);
    //if (!SearchIs_UNC) if (project.schematic) project.schematic(S) check_UNC(S.name);
    //if (!SearchIs_UNC) if (library) library(L) check_UNC(L.name);

    // ************* LINUX File system ****************
    //if (!SearchRootfound) {
    //  pos = strstr(root, "/", 0);
    //  if (pos == 0) {
    //    sprintf(SearchRootfound, "Betriebsystem LINUX");
    //    if (check_files("/", "/")) {
    //      SearchRoot[SearchnRoot] = "/";
    //      SearchnRoot = 1;
    //    }
    //  }
    //}
  }

  int n, r;
  SearchStart = 0;
  SearchEnd = SearchnRoot;
  int iteration = 1;
  int finish = 0;
  int cntf;
  string searchfoundfile[];

  do {
    // 1. die Root-Ordner nach der Datei durchsuchen Eng: Browse the root folders for the file
    for (r = SearchStart; r < SearchEnd; r++) {
      status(SearchRoot[r]);                   // Anzeige des aktuellen Verzeichnisnamen
      n = check_files(SearchRoot[r], searchfile); // suche im Verzeichnis nach Datei
      if (n) {
        for (int f=0; f<n; f++) {
          searchfoundfile[cntf] = SearchFiles[f];
          return searchfoundfile[cntf]; // das erst gefunden File zurückgeben
          cntf++;
        }
      }
    }
    if (finish || (maxiteration && iteration == maxiteration)) break;

    // 2. die Root-Ordner nach Ordnern durchsuchen Eng: Search the root folders for folders
    for (r = SearchStart; r < SearchEnd; r++) {
      sprintf(h, "%d %d %s", iteration, SearchnRoot, SearchRoot[r]);
      status(h);               // Anzeige des aktuellen Verzeichnisnamen
      n = fileglob(a, SearchRoot[r] + "/");      // lesen der Dateien
      if (n) {
        for (int xl = 0; xl < n; xl++) {
          sprintf(h, "%s\n", a[xl]);
          if (a[xl][strlen(a[xl])-1] == '/') { // nach Verzeichnis suchen
            SearchRoot[SearchnRoot] = a[xl];
            sprintf(h, "%d %d %s", iteration, SearchnRoot, SearchRoot[SearchnRoot]);
            status(h);             // Anzeige des aktuellen Verzeichnisnamen
            SearchnRoot++;
          }
          else {
            break;
          }
        }
      }
    }
    SearchStart = r;
    SearchEnd = SearchnRoot; // Suchende erweitern
    if (SearchStart == SearchEnd) {
      finish = 1;
    }
    iteration++;
  } while(SearchnRoot);
  return searchfoundfile[0];
}

string assign_rootpath(string wineused) {
  //This function returns a string containing all the recommended rootpaths for an OS. The calling ULP
  //then parses it to create the rootpath array

  if (OS == "WINDOWS") {
    return "C:/Programme/,C:/Program files (x86)/,C:/Program files/,D:/Program files (x86)/,D:/Program files/";
  }
  if (OS == "LINUX") {
    return EAGLE_HOME+"/.wine/drive_c/Program\ files/,"+EAGLE_HOME+"/.wine/drive_c/Program\ files\ \(x86\)/";
  }
  if (OS == "MAC") {
    if (wineused == "1") {
      // WINE is used
      return "";
    }
    else {
      return "";
    }
  }
  else {
    return "C:/Programme/,C:/Program files (x86)/,C:/Program files/,D:/Program files (x86)/,D:/Program files/";
  }
}

/**********************************************************************************************************************
*                                       EXPORT AND IMPORT FUNCTIONS                                                   *
**********************************************************************************************************************/

// change Eagle slash in path names to backslash for windows
string lash2backslash(string s) {
  int pos;
  if (OS == "WINDOWS") {
	do {
	  pos = strchr(s, '/');
      if (pos >= 0) s[pos] = '\\';
    } while(pos >= 0);
    return s;
  }
  return s;
}


// change backslash in windows path names to Eagle slash
string backslash2lash(string s) {
  int pos;
  if (OS == "WINDOWS") {
    do {
      pos = strchr(s, '\\');
      if (pos >= 0) s[pos] = '/';
    } while(pos >= 0);
    return s;
  }
  return s;
}

string set_directory_path_delimiter(string s) {
  // The objective of this function is to set the delimiters correctly for the OS regardless of what s is
  int pos;
  string regex_string = ":(?!\/)";  //Search for : not followed by /
  
  if (OS == "WINDOWS") {
    do {
      pos = strxstr(s, regex_string); //We found linux delimiter on Windows change it to ;
      if (pos >= 0) s[pos] = ';';
    } while (pos >= 0);
    return s;
  }
  else {
    do {
      pos =strchr(s, ';'); //Found windows delimiter in non-windows os change to :
      if (pos >= 0) s[pos] = ':';
    } while (pos >= 0);
    return s;
  }
}

string checkapostroph(string s) {  // da der ganze String in ' eingeschlossen wird,
                                   // müssen die Apostrophen verdoppelt werden.
  string t[];
  int cnt;
  cnt = strsplit(t, s, '\''); // check Apostroph
  if (cnt > 1) {
    s = "";
    for (int i = 0; i < cnt; i++) {
      if (i == 0) {
        if (t[i]) s += t[i];
      }
      else if (i) s += "''" + t[i];
    }
  }
 return s;
}

int makedir(string root1, string subdir) {  /*** generate DOS command MKDIR ***/
  if (OS == "WINDOWS") {
	string DOScommand;
	sprintf(DOScommand, "CMD.EXE  /C MKDIR \"%s%s\"",  lash2backslash(root1), lash2backslash(subdir));
	system(DOScommand);
	string f[];
	int n = fileglob(f, root1 + subdir); // prüfe ob das Verzeichnis angelegt werden konnte.
	return n;
  }
  else {
	string command;
	sprintf(command, "mkdir \"%s%s\"", lash2backslash(root1), lash2backslash(subdir));
	system(command);
	string f[];
	int n = fileglob(f, root1 + subdir); // Confirm directory was created.
	return n;
  }
}

void call_system(string exportfile, string wineuse) {  // DOS comand execute
  string syscommand;
  done = Debug("Inside call_system");

  if (OS == "WINDOWS") {
	// Das executable und der Dateiname müssen in " " eingeschlossen werden, wegen Spaces im Pfad-Dateinamen!
	sprintf(syscommand, "\"%s\" \"%s\"", lash2backslash(LTSpiceExecute), lash2backslash(exportfile));
	system(syscommand);  // externes Programm starten
	return;
  }
  else {
    if (wineuse == "1") {
      sprintf(syscommand, "wine\ \"%s\"\ \"Z:%s\"", lash2backslash(LTSpiceExecute), lash2backslash(exportfile));
      //In order for Wine to find the file to be imported, you have to reference the linux filesystem from WINE's
      //point of view. WINE maps the linux file system to the z drive by default. I wonder if the MAC behaves the same.
      done = Debug(syscommand);
      system(syscommand);  // start external program
      return;
    }
    else { //This would be MAC running natively
      done = Debug("I'm in the Mac section");
      sprintf(syscommand, "\"%s\" \"%s\"", lash2backslash(LTSpiceExecute), lash2backslash(exportfile));
      system(syscommand);  // externes Programm starten
    }
  }
}

void dosfilecopy( string source, string target, string option) {
  if (OS == "WINDOWS"){
    string DOScommand;
    sprintf(DOScommand, "XCOPY \"%s\" \"%s\" %s", lash2backslash(source), lash2backslash(target), option);
    /*
    dlgDialog("DOS command") {
      dlgHBoxLayout dlgSpacing(800);
      dlgStringEdit(DOScommand);
        dlgPushButton("ok") dlgAccept();
        dlgPushButton("esc") { dlgReject(); exit(-4056); }
      };
    */
    system(DOScommand);
    return;
  }
  else {
    if (option == "/S /Y") {
      // The above options want a recursive function with no overwrite confirmation. That's what I've implemented below
      string command;
      sprintf(command, "yes | cp -rf \"%s\" \"%s\"", lash2backslash(source), lash2backslash(target));
      system(command);
    }
    return;
  }
}
